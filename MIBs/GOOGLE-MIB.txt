GOOGLE-MIB DEFINITIONS ::= BEGIN

-- The root MIB for Google Inc.

IMPORTS 
        OBJECT-TYPE, MODULE-IDENTITY,
	enterprises FROM SNMPv2-SMI;

google MODULE-IDENTITY
	LAST-UPDATED "200407161000Z"
	ORGANIZATION "Google Inc."
	CONTACT-INFO
	    "This MIB is the root for all enterprise
	     specific SNMP varibales exposed by Google's
	     products
	
	     postal:	Ian Macdonald
			1600 Amphitheatre Pkwy
			Mountain View, CA 94035

	     email:	appliance-support@google.com
	    "
	DESCRIPTION
	    "Initial Version for Google's root MIB"
	::= { enterprises 11129 }

-- Following are the different groups in google's MIB tree

-- Google Search Appliance
gsa 	OBJECT IDENTIFIER ::= { google 1 }

END
