SYNOLOGY-RAID-MIB DEFINITIONS ::= BEGIN

IMPORTS
	enterprises
				FROM SNMPv2-SMI
    DisplayString
				FROM SNMPv2-TC
    OBJECT-TYPE, INTEGER
				FROM SNMPv2-SMI
	synology 
				FROM SYNOLOGY-DISK-MIB;

synoRaid	OBJECT IDENTIFIER
	::= { synology 3 }

RaidTable OBJECT-TYPE
    SYNTAX	   SEQUENCE OF SynoRaidTable
    MAX-ACCESS	  not-accessible
    STATUS	   current
    DESCRIPTION
    "Synology raid table"
    ::= { synoRaid 1 }

RaidEntry	  OBJECT-TYPE
    SYNTAX	   RaidEntry
    MAX-ACCESS	  not-accessible
    STATUS	   current
    DESCRIPTION
    "For all raid entry"
    INDEX   { RaidIndex }
    ::= { RaidTable 1 }

RaidEntry ::= SEQUENCE {
    RaidIndex		INTEGER,
    RaidName		OCTET STRING,
	RaidStatus		INTEGER
}

RaidIndex OBJECT-TYPE
    SYNTAX	   INTEGER
    MAX-ACCESS	  not-accessible
    STATUS	   current
    DESCRIPTION
    "The index of raid table"
    ::= { RaidEntry 1 }

RaidName OBJECT-TYPE
    SYNTAX	  OCTET STRING
    MAX-ACCESS  read-only
    STATUS	  current
    DESCRIPTION
    "Synology raid name
	 The name of each raid will be showed here.
	"
    ::= { RaidEntry 2 }

RaidStatus OBJECT-TYPE
    SYNTAX	  INTEGER {
					Normal(1),
					Repairing(2),
					Migrating(3),
					Expanding(4),
					Deleting(5),
					Creating(6),
					RaidSyncing(7),
					RaidParityChecking(8),
					RaidAssembling(9),
					Canceling(10),
					Degrade(11),
					Crashed(12)
			  }
    MAX-ACCESS  read-only
    STATUS	  current
    DESCRIPTION
    "Synology Raid status
	 Each meanings of status represented describe below.
	 Normal(1): The raid functions normally.
 	 Degrade(11): Degrade happens when a tolerable failure of disk(s) occurs.
 	 Crashed(12): Raid has crashed and just uses for read-only operation.

	 Note:
	 Other status will be showed when creating or deleting raids, including below status, Repairing(2), Migrating(3), Expanding(4), Deleting(5), Creating(6), RaidSyncing(7), RaidParityChecking(8), RaidAssembling(9) and Canceling(10).
	"
    ::= { RaidEntry 3 }

END
